--- Протокол Месенжера Сохацького v2 для паб-саб брокерів на TLS
--- https://tonpa.guru/stream/2023/2023-08-07 CHAT ASN.1.htm

CHAT-v2 DEFINITIONS IMPLICIT TAGS ::=
BEGIN
    -- CHAT-v2 design direction
    --
    -- Архітектурна мета:
    --   1. CHATProtocol містить тільки transport-level packet types.
    --   2. Message описує тільки контент повідомлення.
    --   3. Event є єдиним каналом runtime-подій (ack/activity/state updates).
    --   4. Query є єдиним request/response механізмом.
    --   5. Domain сутності (Subscription, Person, Member, Conference, Roster, Inbox view)
    --      не повинні бути top-level packet types.
    --
    -- Цільова модель:
    --   state   -> окремі domain/resource типи
    --   command -> Query
    --   event   -> Event
    --
    -- Тобто одна семантика не повинна мати кілька паралельних wire-шляхів.

    IMPORTS ContentInfo FROM CryptographicMessageSyntax-2009
            CertificationRequest FROM PKCS-10
            Certificate FROM PKIX1Explicit-2009 ;

    Version ::= INTEGER  { v0(0), v1(1), v2(2), v3(3) }
    OS ::= ENUMERATED { apple (1), microsoft (2), google (3), ericsson (4), nokia (5), cisco (6) }

    -- 01 Authority (CA)

    Feature ::= SEQUENCE { id OCTET STRING, key OCTET STRING, value OCTET STRING, group OCTET STRING }
    AuthorityMethod ::= ENUMERATED { announce (0), enroll (1), authenticate (2), revoke (3), renew (4), ... }
    Authority ::= SEQUENCE {
       id OCTET STRING,
       vsn Version,
       session OCTET STRING,
       type AuthorityMethod,
       cert OCTET STRING,
       settings SEQUENCE OF feature Feature,
        ... }

    -- 02 Message (MNESIA, SQLite)

    -- Message описує тільки саме повідомлення і його вміст.
    -- Event є уніфікованим типом для всіх подій (Ack + Activity).
    -- Такий поділ мінімізує розмір базових повідомлень і не змішує семантику.

    MessageType ::= ENUMERATED { normal (0), sys (1), reply (2), forward (3), ... }

    MessageFeed ::= CHOICE { private [1] Privatebox, chan [2] Streambox, mailbox [4] Mailbox, group [8] Groupbox }

    Message ::= SEQUENCE {
       id OCTET STRING,
       vsn Version,
       session OCTET STRING,

       -- базовий мінімум
       feed MessageFeed,
       payload ContentInfo,

       -- optional атрибути
       type MessageType OPTIONAL,
       linkId OCTET STRING OPTIONAL,
       files SEQUENCE OF fileId OCTET STRING OPTIONAL,
       mentioned SEQUENCE OF name OCTET STRING OPTIONAL,
       ...
    }

    -- 03 Inbox Folder Queue (MNESIA, SQLite) /Mail /Chat

    Privatebox ::= SEQUENCE { address OCTET STRING }
    Streambox ::= SEQUENCE { channel OCTET STRING }
    Groupbox ::= SEQUENCE { channel OCTET STRING }
    Mailbox ::= SEQUENCE { channel OCTET STRING }

    InboxMethod ::= ENUMERATED { get (1), erase (2), ...}

    Inbox ::= SEQUENCE {
       id OCTET STRING,
       vsn Version,
       session OCTET STRING,
       type InboxMethod,
       feed MessageFeed,
       messages SEQUENCE OF message Message,
        ...}

    InboxOp ::= ENUMERATED {
       get   (1),
       erase (2),
       ...
    }

    -- get/erase працюють у межах конкретного feed
    -- для обох операцій feed очікується
    InboxQueryRequest ::= SEQUENCE {
       op    InboxOp,
       feed  MessageFeed OPTIONAL,
       ...
    }

    InboxItem ::= SEQUENCE {
       message Message
    }

    -- result повертає набір елементів inbox для feed (може бути пустим)
    InboxQueryResult ::= SEQUENCE {
       items SEQUENCE OF item InboxItem OPTIONAL,
       ...
    }

    -- 04 Event (Ack + Activity fusion)
    --
    -- Event є єдиним каналом runtime-подій.
    -- Події групуються за family payload, без глобального плаского enum.
    -- Для простих family тип події задається локальним enum усередині payload.

    MessageEventType ::= ENUMERATED {
       received  (1),
       delivered (2),
       read      (3),
       edited    (4),
       deleted   (5),
       updated   (6), ...}

    MessageEvent ::= SEQUENCE {
       type       MessageEventType,
       messageId  OCTET STRING OPTIONAL,
       feed       MessageFeed OPTIONAL,
       actor      OCTET STRING OPTIONAL,
       timestamp  INTEGER OPTIONAL -- unix time (ms),
       ...
    }

    PresenceEventType ::= ENUMERATED {
       online   (1),
       offline  (2),
       typing   (3), ...}

    PresenceEvent ::= SEQUENCE {
       type       PresenceEventType,
       feed       MessageFeed OPTIONAL,
       actor      OCTET STRING OPTIONAL,
       timestamp  INTEGER OPTIONAL,
       ...
    }

    EventPayload ::= CHOICE {
       message   [1] MessageEvent,
       presence  [2] PresenceEvent
    }

    Event ::= SEQUENCE {
       id OCTET STRING,
       vsn Version,
       session OCTET STRING,
       payload EventPayload,
       ...
    }

    -- Query є єдиним request/response шаром протоколу.
    -- Усі commands і state-запити повинні йти через Query.
    -- Payload уже розбитий на доменні family envelope.
    -- Внутрішні request/result payload типи тимчасово залишаються opaque
    -- до поступової типізації кожної family окремо.

    QueryType ::= ENUMERATED {
       get    (1),
       set    (2),
       result (3),
       error  (4), ...}

    Query ::= SEQUENCE {
       id OCTET STRING,
       vsn Version,
       session OCTET STRING,

       queryType QueryType,

       refId OCTET STRING OPTIONAL, -- request correlation id
       feed MessageFeed OPTIONAL,
       target OCTET STRING OPTIONAL, -- optional routing hint; domain target belongs in payload
       payload QueryPayload OPTIONAL, -- typed query family payload
       code INTEGER OPTIONAL,
       ...
    }

    QueryPayload ::= CHOICE {
       subscription [1] SubscriptionQueryEnvelope,
       presence     [2] PresenceQueryEnvelope,
       person       [3] PersonQueryEnvelope,
       member       [4] MemberQueryEnvelope,
       roster       [5] RosterQueryEnvelope,
       conference   [6] ConferenceQueryEnvelope,
       inbox        [7] InboxQueryEnvelope,
       search       [8] SearchQueryEnvelope,
       moderation   [9] ModerationQueryEnvelope,
       ...
    }

    SubscriptionQueryEnvelope ::= CHOICE {
       request [1] SubscriptionQueryRequest,
       result  [2] SubscriptionQueryResult
    }

    PresenceQueryEnvelope ::= CHOICE {
       request [1] PresenceQueryRequest,
       result  [2] PresenceQueryResult
    }

    PersonQueryEnvelope ::= CHOICE {
       request [1] PersonQueryRequest,
       result  [2] PersonQueryResult
    }

    MemberQueryEnvelope ::= CHOICE {
       request [1] MemberQueryRequest,
       result  [2] MemberQueryResult
    }

    InboxQueryEnvelope ::= CHOICE {
       request [1] InboxQueryRequest,
       result  [2] InboxQueryResult
    }

    -- 05 Search (LDAP Search)

    SearchStatus ::= ENUMERATED { ok (0), ...}
    Criteria ::= ENUMERATED { equal (0), notequal (1), like (2), ...}
    Scope ::= ENUMERATED { profile (0), folder (1), contact (2), member (3), room (4), chat (5), message (6), ...}

    SearchOp ::= ENUMERATED {
       execute (1),
       list    (2),
       ...
    }

    -- execute використовує field/value/criteria/type
    -- list допускає частковий фільтр або перегляд у межах scope/dn
    SearchQueryRequest ::= SEQUENCE {
       op       SearchOp,
       dn       OCTET STRING OPTIONAL,
       field    OCTET STRING OPTIONAL,
       value    OCTET STRING OPTIONAL,
       criteria Criteria OPTIONAL,
       type     Scope OPTIONAL,
       ...
    }

    SearchItem ::= SEQUENCE {
       dn       OCTET STRING OPTIONAL,
       field    OCTET STRING OPTIONAL,
       value    OCTET STRING OPTIONAL,
       criteria Criteria OPTIONAL,
       type     Scope OPTIONAL
    }

    -- result повертає список знайдених елементів (може бути пустим)
    SearchQueryResult ::= SEQUENCE {
       items SEQUENCE OF item SearchItem OPTIONAL,
       ...
    }

    SearchQueryEnvelope ::= CHOICE {
       request [1] SearchQueryRequest,
       result  [2] SearchQueryResult
    }

    -- 06 Subscription (зв'язок підписки між суб'єктом і ціллю)
    --
    -- Модель спрощена до факту зв'язку (actor -> target).
    -- Жодних статусів або presence тут більше немає.
    --
    -- Перенесення семантики:
    --
    -- Presence (online/offline/typing):
    --   → перенесено в Event
    --
    -- Lifecycle дії (request/confirm/ignore/ban/unban):
    --   → передаються через Event (як події)
    --   → або ініціюються через Query (type=set)
    --
    -- Бан:
    --   → не є частиною Subscription
    --   → є server-side policy (обмеження доступу)
    --   → встановлюється через Query і сигналізується через Event
    --
    -- Таким чином:
    --   Subscription = state (факт зв'язку)
    --   Event        = що сталося (події)
    --   Query        = як це змінити / отримати

    Subscription ::= SEQUENCE {
       actor  OCTET STRING,
       target OCTET STRING,
       ...
    }

    -- get/create/remove очікують actor + target
    -- list допускає частковий фільтр
    SubscriptionQueryRequest ::= SEQUENCE {
       op     SubscriptionOp,
       actor  OCTET STRING OPTIONAL,
       target OCTET STRING OPTIONAL,
       ...
    }

    SubscriptionOp ::= ENUMERATED {
       get    (1),
       list   (2),
       create (3),
       remove (4),
       ...
    }

    -- get/create/remove зазвичай повертають item
    -- list повертає items
    SubscriptionQueryResult ::= SEQUENCE {
       item   Subscription OPTIONAL,
       items  SEQUENCE OF subscription Subscription OPTIONAL,
       ...
    }

    -- 07 Roster (LDAP /People, /Channels, /Topics and /Servers user sub-folders)

    -- Presence як snapshot-стан для roster/member.
    -- Runtime presence-події (online/offline/typing) передаються через Event.

    Presence ::= ENUMERATED { offline (1), online (2), ... }

    PresenceOp ::= ENUMERATED {
       get  (1),
       list (2), ...
    }

    -- get зазвичай очікує actor
    -- list допускає actor і/або feed як фільтр вибірки
    -- feed задає контекст (якщо presence залежить від feed)
    PresenceQueryRequest ::= SEQUENCE {
       op     PresenceOp,
       actor  OCTET STRING OPTIONAL,
       feed   MessageFeed OPTIONAL,
       ...
    }

    PresenceItem ::= SEQUENCE {
       actor     OCTET STRING,
       presence  Presence
    }

    -- get зазвичай повертає item
    -- list повертає items (може бути пустим)
    PresenceQueryResult ::= SEQUENCE {
       item   PresenceItem OPTIONAL,
       items  SEQUENCE OF item PresenceItem OPTIONAL,
       ...
    }


    -- PersonStatus описує лише стан самого profile/state запису.
    -- Relation, lifecycle і moderation більше не живуть у Person:
    --   req/auth/ignore/friend -> Subscription / Event
    --   ban/banned             -> ModerationQuery / Event
    PersonStatus ::= ENUMERATED {
       active      (1),
       deleted     (2),
       nonexistent (3), ...
    }

    -- lastmsg не є частиною Person state.
    -- View-дані повинні передаватися через Query (Inbox/Search) або Event.
    Person ::= SEQUENCE {
       id OCTET STRING,
       nickname OCTET STRING,
       avatar OCTET STRING,
       names SEQUENCE OF name OCTET STRING,
       phone OCTET STRING,
       surnames SEQUENCE OF name OCTET STRING,

       presence Presence,

       update INTEGER,
       created INTEGER,

       settings SEQUENCE OF feature Feature OPTIONAL,

       status PersonStatus,
       ...
    }

    PersonOp ::= ENUMERATED {
       get    (1),
       list   (2),
       update (3),
       remove (4), ...
    }

    -- get/remove очікують id
    -- update використовує поля профілю
    -- list допускає частковий фільтр
    PersonQueryRequest ::= SEQUENCE {
       op   PersonOp,

       id   OCTET STRING OPTIONAL,
       name OCTET STRING OPTIONAL,
       ...
    }

    PersonItem ::= SEQUENCE {
       id       OCTET STRING,
       nickname OCTET STRING,
       presence Presence,
       status   PersonStatus
    }

    -- get/update зазвичай повертають item
    -- list повертає items
    PersonQueryResult ::= SEQUENCE {
       item   PersonItem OPTIONAL,
       items  SEQUENCE OF item PersonItem OPTIONAL,
       ...
    }

    Server ::= SEQUENCE { service OCTET STRING, port INTEGER, host OCTET STRING }

    -- RosterStatus описує лише стан roster як ресурсу.
    -- Command, mutation і lookup більше не живуть у Roster:
    --   get/create/del/remove/add/update/list/patch -> Query
    --   nick/search/contact/lastmsg                 -> Query / view
    RosterStatus ::= ENUMERATED {
       active   (1),
       archived (2),
       deleted  (3), ...
    }

    -- Roster є агрегованим snapshot/view ресурсом.
    -- Операції над roster передаються через Query.
    -- Runtime-події не живуть у Roster як моделі.
    Roster ::= SEQUENCE {
       id OCTET STRING,
       vsn Version,
       session OCTET STRING,
       nickname OCTET STRING,
       keys SEQUENCE OF key OCTET STRING,
       people SEQUENCE OF contact Person,
       topics SEQUENCE OF room Conference,
       channels SEQUENCE OF room Conference,
       servers SEQUENCE OF server Server,
       update INTEGER,
       status RosterStatus, ... }

    RosterOp ::= ENUMERATED {
       get  (1),
       list (2), ...
    }

    -- get зазвичай очікує id
    -- list допускає частковий фільтр
    RosterQueryRequest ::= SEQUENCE {
       op   RosterOp,

       id   OCTET STRING OPTIONAL,
       name OCTET STRING OPTIONAL,
       ...
    }

    RosterItem ::= SEQUENCE {
       id       OCTET STRING,
       nickname OCTET STRING,
       status   RosterStatus
    }

    -- get зазвичай повертає item
    -- list повертає items
    RosterQueryResult ::= SEQUENCE {
       item   RosterItem OPTIONAL,
       items  SEQUENCE OF item RosterItem OPTIONAL,
       ...
    }

    RosterQueryEnvelope ::= CHOICE {
       request [1] RosterQueryRequest,
       result  [2] RosterQueryResult
    }

    ModerationOp ::= ENUMERATED {
       ban    (1),
       unban  (2),
       list   (3), ...
    }

    -- ban/unban очікують actor + target
    -- list повертає список обмежень
    ModerationQueryRequest ::= SEQUENCE {
       op     ModerationOp,

       actor  OCTET STRING OPTIONAL,
       target OCTET STRING OPTIONAL,
       ...
    }

    ModerationItem ::= SEQUENCE {
       actor   OCTET STRING,
       target  OCTET STRING
    }

    -- ban/unban зазвичай повертають item
    -- list повертає items
    ModerationQueryResult ::= SEQUENCE {
       item   ModerationItem OPTIONAL,
       items  SEQUENCE OF item ModerationItem OPTIONAL,
       ...
    }

    ModerationQueryEnvelope ::= CHOICE {
       request [1] ModerationQueryRequest,
       result  [2] ModerationQueryResult
    }

    -- 08 Conference (RocksDB, Multi-user Conferences)

    -- MemberStatus описує лише роль учасника в конференції.
    -- Lifecycle і mutation більше не живуть у Member:
    --   removed        -> Event / Query
    --   patch/update   -> Query
    MemberStatus ::= ENUMERATED {
       member (1),
       admin  (2),
       owner  (3), ...}

    Member ::= SEQUENCE {
       id OCTET STRING,
       nickname OCTET STRING,
       feed MessageFeed,
       feeds SEQUENCE OF feed OCTET STRING,
       phone OCTET STRING,
       avatar OCTET STRING,
       names SEQUENCE OF name OCTET STRING,
       surnames SEQUENCE OF name OCTET STRING,
       alias OCTET STRING,
       update INTEGER,
       settings SEQUENCE OF feature Feature,
       presence Presence,
       status MemberStatus, ... }

    MemberOp ::= ENUMERATED {
       get    (1),
       list   (2),
       add    (3),
       remove (4),
       update (5)
    }

    -- get/remove/update очікують actor + feed
    -- add використовує actor + feed
    -- list допускає фільтр за feed
    MemberQueryRequest ::= SEQUENCE {
       op    MemberOp,

       actor OCTET STRING OPTIONAL,
       feed  MessageFeed OPTIONAL
    }

    MemberItem ::= SEQUENCE {
       actor   OCTET STRING,
       feed    MessageFeed,
       status  MemberStatus,
       presence Presence OPTIONAL
    }

    -- get/add/update зазвичай повертають item
    -- list повертає items
    MemberQueryResult ::= SEQUENCE {
       item   MemberItem OPTIONAL,
       items  SEQUENCE OF item MemberItem OPTIONAL
    }

    ConferenceType ::= ENUMERATED { group (1), channel (2), call (3) }

    -- ConferenceStatus описує лише стан конференції як ресурсу.
    -- Command, lifecycle і події більше не живуть у Conference:
    --   create/add/remove/patch/get/delete -> Query
    --   join/leave/joined/removed          -> Event
    --   mute/unmute                        -> Query / Event
    --   lastmsg                            -> Query (Inbox/Search) або Event
    ConferenceStatus ::= ENUMERATED {
       active   (1),
       archived (2),
       deleted  (3), ...
    }

    -- lastmsg не є частиною Conference state.
    -- View-дані повинні передаватися через Query (Inbox/Search) або Event.
    Conference ::= SEQUENCE {
       id OCTET STRING,
       vsn Version,
       session OCTET STRING,
       name OCTET STRING,
       links SEQUENCE OF link OCTET STRING,
       description OCTET STRING,
       settings SEQUENCE OF feature Feature,
       members SEQUENCE OF member Member,
       admins SEQUENCE OF member Member,
       data SEQUENCE OF fileId OCTET STRING OPTIONAL,
       type ConferenceType,
       tos OCTET STRING,
       unread INTEGER,
       mentions SEQUENCE OF contact INTEGER,
       update INTEGER,
       created INTEGER,
       status ConferenceStatus,
        ... }

    ConferenceOp ::= ENUMERATED {
       get     (1),
       list    (2),
       create  (3),
       update  (4),
       remove  (5), ...
    }

    -- get/remove очікують id
    -- create/update використовують поля конференції
    -- list допускає частковий фільтр
    ConferenceQueryRequest ::= SEQUENCE {
       op    ConferenceOp,

       id    OCTET STRING OPTIONAL,
       name  OCTET STRING OPTIONAL,
       type  ConferenceType OPTIONAL,
       ...
    }

    -- get/create/update зазвичай повертають item
    -- list повертає items
    ConferenceQueryResult ::= SEQUENCE {
       item   ConferenceItem OPTIONAL,
       items  SEQUENCE OF item ConferenceItem OPTIONAL,
       ...
    }

    ConferenceItem ::= SEQUENCE {
       id    OCTET STRING,
       name  OCTET STRING,
       type  ConferenceType,
       status ConferenceStatus
    }

    ConferenceQueryEnvelope ::= CHOICE {
       request [1] ConferenceQueryRequest,
       result  [2] ConferenceQueryResult
    }

    -- 09 CHAT-v2 Protocol Entities

    CHATProtocol ::= CHOICE {
       authority [1] Authority,
       message   [2] Message,
       event     [4] Event,
       query     [5] Query
    }

    CHATMessage ::= SEQUENCE {
       no INTEGER,
       headers SEQUENCE OF header OCTET STRING,
       body CHATProtocol }

END
