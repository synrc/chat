List DEFINITIONS EXPLICIT TAGS ::= BEGIN

  Real ::= SEQUENCE {
    mantissa INTEGER,
    base INTEGER (2|10),
    exponent INTEGER }

  X ::= SET {
    a INTEGER,
    b SET OF OCTET STRING,
    d Real
  }

  V ::= SEQUENCE {
    a [1] INTEGER (0..7),
    b [2] BOOLEAN,
    version INTEGER { v1(1) },
    c INTEGER (0..3),
    d SEQUENCE { d1 BOOLEAN, d2 BOOLEAN } }

  Versioning ::= INTEGER {  v1(0) }

  A ::= CHOICE {
    v [0] V,
    list-x [1] List,
    o [2] SET OF OCTET STRING,
    s [3] SEQUENCE OF OCTET STRING }

  List ::= SEQUENCE {
    data OCTET STRING,
    next CHOICE { linked-list List, end NULL, ss [1] SET OF OCTET STRING } }

END
